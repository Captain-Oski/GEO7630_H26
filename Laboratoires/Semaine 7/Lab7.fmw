FME workspace Lab7.fmw

Parameters:
- SourceDataset_CSV2 =
- SourceDataset_CSV2_3 =

Readers:
- CSV2_1: CSV2 from $(SourceDataset_CSV2)
- CSV2_2: CSV2 from $(SourceDataset_CSV2_3)
- ARCGISONLINEFEATURES_1: ARCGISONLINEFEATURES

Writers:
- ARCGISONLINEFEATURES_2: ARCGISONLINEFEATURES
- ARCGISONLINEFEATURES_3: ARCGISONLINEFEATURES

Note: https://sitewebbixi.s3.amazonaws.com/uploads/docs/20220107-donnees-ouvertes-8aa623.zip
CSV (reader CSV2_1) [off]
    attributes: start_date varchar(24), emplacement_pk_start uint32, end_date varchar(24), emplacement_pk_end uint32, duration_sec uint32, is_member uint32, latitude y_coordinate, longitude x_coordinate, name varchar(68), pk uint32
    -> AttributeFilter
Note: https://sitewebbixi.s3.amazonaws.com/uploads/docs/20220108-donnees-ouvertes-816bd4.zip
CSV (reader CSV2_2)
    attributes: start_date varchar(24), emplacement_pk_start uint32, end_date varchar(24), emplacement_pk_end uint32, duration_sec uint32, is_member uint32, latitude y_coordinate, longitude x_coordinate, name varchar(68), pk uint32
    -> AttributeFilter
Note: Écrire le CSV dans ArcGIS Online
CSV (writer ARCGISONLINEFEATURES_3)
    attributes: name String(68), pk Integer, start_total_count Integer, end_total_count Integer

Bookmark: Juillet 2022
Note: Cela va filtrer les entités qui ne possède pas la propriété (longitude) Parce qu’il y a 2 csv dans le .zip, les stations et les origines et destinations (sans les coordonnées lat long des stations).
AttributeFilter
    ATTR_NAME = longitude
    ATTR_VALUES = <Empty>,<Missing>,<Null>,<Unfiltered>,-1
    <MISSING> -> StatisticsCalculator
    <MISSING> -> StatisticsCalculator_2
    <UNFILTERED> -> AttributeManager
Note: OD: Total des arrivées
StatisticsCalculator
    CALCULATION_MODE = NUMERIC
    FEAT_STATS = emplacement_pk_end,NUMERIC_MODE,,,COUNT,,,,,,,,,,
    GROUP_BY = emplacement_pk_end
    SUMMARY -> FeatureJoiner_2 [RIGHT]
Note: OD: Total des départs
StatisticsCalculator_2
    CALCULATION_MODE = NUMERIC
    FEAT_STATS = emplacement_pk_start,NUMERIC_MODE,,,COUNT,,,,,,,,,,
    GROUP_BY = emplacement_pk_start
    SUMMARY -> FeatureJoiner [RIGHT]
Note: STATIONS : Suppression des attributs non nécessaires
AttributeManager
    ATTR_TABLE:
      REMOVE start_date
      REMOVE emplacement_pk_start
      REMOVE end_date
      REMOVE emplacement_pk_end
      REMOVE duration_sec
      REMOVE is_member
      REMOVE latitude
      REMOVE longitude
    -> FeatureJoiner [LEFT]
Note: Calculer la somme des départs par station
FeatureJoiner
    ATTR_CONFLICT_RES = Use Left
    GEOMETRY_HANDLING = Use Left
    JOIN_KEYS = pk emplacement_pk_start AUTO
    JOIN_MODE = Full
    JOINED -> FeatureJoiner_2 [LEFT]
    <REJECTED> -> FeatureJoiner__Rejected_
Note: Calculer la somme des arrivées par station
FeatureJoiner_2
    ATTR_CONFLICT_RES = Use Left
    GEOMETRY_HANDLING = Use Left
    JOIN_KEYS = pk emplacement_pk_end AUTO
    JOIN_MODE = Full
    JOINED -> AttributeManager_2
    <REJECTED> -> FeatureJoiner_2__Rejected_
Note: Un peu de ménage
AttributeManager_2
    ATTR_TABLE:
      REMOVE emplacement_pk_start
      RENAME_SET_VALUE emplacement_pk_start.total_count > start_total_count
      REMOVE emplacement_pk_end
      RENAME_SET_VALUE emplacement_pk_end.total_count > end_total_count
    -> ChangeDetector [REVISED]
    -> CSV (writer ARCGISONLINEFEATURES_3)
FeatureJoiner_2__Rejected_: Logger
    LOG_FEATURE = LOG_ONLY
    MAXCOORDS = 20
    MAXFEATS = 20
    MESSAGE = Feature is:
    SEVERITY = INFO
FeatureJoiner__Rejected_: Logger
    LOG_FEATURE = LOG_ONLY
    MAXCOORDS = 20
    MAXFEATS = 20
    MESSAGE = Feature is:
    SEVERITY = INFO

Bookmark: Update Aout 2022
CSV (reader ARCGISONLINEFEATURES_1)
    attributes: name String(68), pk Integer, start_total_count Integer, end_total_count Integer, OBJECTID OID
    -> ChangeDetector [ORIGINAL]
    -> FeatureJoiner_3 [LEFT]
ChangeDetector
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCHATTRS = end_total_count name pk start_total_count
    MATCH_STRATEGY = Match Selected Attributes
    PREEMPTIVE_ATTRS = pk
    UNCHANGED_OUTPUT = Output Both
    UPDATED -> FeatureJoiner_3 [RIGHT]
FeatureJoiner_3
    ATTR_CONFLICT_RES = Use Left
    GEOMETRY_HANDLING = Use Left
    JOIN_KEYS = pk pk AUTO
    JOIN_MODE = Inner
    JOINED -> AttributeManager_3
    <REJECTED> -> FeatureJoiner_3__Rejected_
AttributeManager_3
    ATTR_TABLE = REMOVE fme_db_operation
    -> CSV (writer ARCGISONLINEFEATURES_2)
CSV (writer ARCGISONLINEFEATURES_2)
    attributes: name String(68), pk Integer, start_total_count Integer, end_total_count Integer
FeatureJoiner_3__Rejected_: Logger
    LOG_FEATURE = LOG_ONLY
    MAXCOORDS = 20
    MAXFEATS = 20
    MESSAGE = Feature is:
    SEVERITY = INFO
